module gobgp {

  yang-version "1";

  // namespace
  namespace "https://github.com/osrg/gobgp";

  prefix "gobgp";

  // import some basic types
  import openconfig-bgp { prefix bgp; }
  import openconfig-bgp-types { prefix bgp-types; }
  import openconfig-bgp-multiprotocol { prefix bgp-mp; }
  import openconfig-routing-policy {prefix rpol; }
  import openconfig-policy-types {prefix ptypes; }
  import openconfig-bgp-policy {prefix bgp-pol; }
  import ietf-inet-types { prefix inet; }
  import ietf-yang-types { prefix yang; }

  // meta
  organization
    "GoBGP";

  contact
    "GoBGP http://osrg.github.io/gobgp/";

  description
    "This module contains definitions for GoBGP-specific configuration.
    It augments bgp modules with GoBGP-specific options.";

  revision "2015-08-10" {
    description
      "Updated model to augment base bgp modules";
    reference "TBD";
  }

  typedef bmp-route-monitoring-policy-type {
    type enumeration {
      enum PRE-POLICY {
        value 0;
        description "send pre-policy routes";
      }
      enum POST-POLICY {
        value 1;
        description "send post-policy routes";
      }
      enum BOTH {
        value 2;
        description "!OBSOLETED! send both pre and post-policy routes";
      }
      enum LOCAL-RIB {
        value 3;
        description "send local rib routes";
      }
      enum ALL {
        value 4;
        description "send pre-policy, post-policy, and local rib routes";
      }
    }
  }

  identity eq {
      base ptypes:attribute-comparison;
  }

  identity ge {
      base ptypes:attribute-comparison;
  }

  identity le {
      base ptypes:attribute-comparison;
  }

  identity IPV4-MULTICAST {
    base bgp-types:afi-safi-type;
    description
      "IPv4 multicast (AFI,SAFI = 1,2)";
    reference "RFC4760";
  }

  identity IPV6-MULTICAST {
    base bgp-types:afi-safi-type;
    description
      "IPv4 multicast (AFI,SAFI = 1,2)";
    reference "RFC4760";
  }

  identity RTC {
    base bgp-types:afi-safi-type;
    description
      "Route target membership (AFI,SAFI = 1,132)";
    reference "RFC4684";
  }

  identity IPV4-ENCAP {
    base bgp-types:afi-safi-type;
    description
      "Encapsulation (AFI,SAFI = 1,7)";
    reference "RFC5512";
  }

  identity IPV6-ENCAP {
    base bgp-types:afi-safi-type;
    description
      "Encapsulation (AFI,SAFI = 2,7)";
    reference "RFC5512";
  }

  identity IPV4-FLOWSPEC {
    base bgp-types:afi-safi-type;
    description
      "IPv4 flowspec (AFI,SAFI = 1,133)";
    reference "RFC5575";
  }

  identity L3VPN-IPV4-FLOWSPEC {
    base bgp-types:afi-safi-type;
    description
      "L3VPN IPv4 flowspec (AFI,SAFI = 1,134)";
    reference "RFC5575";
  }

  identity IPV6-FLOWSPEC {
    base bgp-types:afi-safi-type;
    description
      "IPv6 flowspec (AFI,SAFI = 1,133)";
    reference "RFC5575";
  }

  identity L3VPN-IPV6-FLOWSPEC {
    base bgp-types:afi-safi-type;
    description
      "L3VPN IPv6 flowspec (AFI,SAFI = 1,134)";
    reference "RFC5575";
  }

  identity L2VPN-FLOWSPEC {
    base bgp-types:afi-safi-type;
    description
      "L2VPN flowspec (AFI,SAFI = 25,134)";
    reference "draft-ietf-idr-flowspec-l2vpn-03";
  }

  identity IPV4-SRPOLICY {
    base bgp-types:afi-safi-type;
    description
      "SR Policy IPv4 (AFI,SAFI = 1,73)";
    reference "https://tools.ietf.org/html/draft-ietf-idr-segment-routing-te-policy-11";
  }

  identity IPV6-SRPOLICY {
    base bgp-types:afi-safi-type;
    description
      "SR Policy IPv6 (AFI,SAFI = 2,73)";
    reference "https://tools.ietf.org/html/draft-ietf-idr-segment-routing-te-policy-11";
  }

  identity OPAQUE {
    base bgp-types:afi-safi-type;
    description
      "Opaque (AFI,SAFI = 16397,241)";
    reference "https://tools.ietf.org/html/draft-lapukhov-bgp-opaque-signaling-01";
  }

  identity LS {
    base bgp-types:afi-safi-type;
    description
      "Linkstate (AFI,SAFI = 16388,71)";
    reference "RFC7752";
  }

  identity IPV4-MUP {
    base bgp-types:afi-safi-type;
    description
      "MUP IPv4 (AFI,SAFI = 1,85)";
    reference "https://www.ietf.org/archive/id/draft-ietf-bess-mup-safi-01.html";
  }

  identity IPV6-MUP {
    base bgp-types:afi-safi-type;
    description
      "MUP IPv6 (AFI,SAFI = 2,85)";
    reference "https://www.ietf.org/archive/id/draft-ietf-bess-mup-safi-01.html";
  }

  grouping gobgp-message-counter {
    description
      "Counters for all BGPMessage types";

    leaf OPEN {
      type uint64;
      description
        "Number of BGP open messages announcing, withdrawing
        or modifying paths exchanged.";
    }

    leaf REFRESH {
      type uint64;
      description
        "Number of BGP Route-Refresh messages indicating an
        error condition has occurred exchanged.";
    }

    leaf KEEPALIVE {
      type uint64;
      description
        "Number of BGP Keepalive messages indicating an
        error condition has occurred exchanged.";
    }

    leaf DYNAMIC-CAP {
      type uint64;
      description
        "Number of BGP dynamic-cap messages indicating an
        error condition has occurred exchanged.";
    }

    leaf WITHDRAW-UPDATE {
      type uint32;
      description
        "Number of updates subjected to treat-as-withdraw treatment.";
    }

    leaf WITHDRAW-PREFIX {
      type uint32;
      description
        "Number of prefixes subjected to treat-as-withdraw treatment.";
    }

    leaf DISCARDED {
      type uint64;
      description
        "Number of discarded messages indicating an
        error condition has occurred exchanged.";
    }

    leaf TOTAL {
      type uint64;
      description
        "Number of total messages indicating an
        error condition has occurred exchanged.";
    }
  }

  grouping gobgp-adjacent-table {
    container adj-table {
      leaf ADVERTISED {
        type uint32;
      }

      leaf FILTERED {
        type uint32;
      }

      leaf RECEIVED {
        type uint32;
      }

      leaf ACCEPTED {
        type uint32;
      }
    }
  }


  grouping gobgp-timer {
    description "additional timer";

    leaf idle-hold-time-after-reset {
      type decimal64 {
        fraction-digits 2;
      }
      default 30;
      description
        "Time interval in seconds that a BGP session will be
        in idle state after neighbor reset operation.";
    }
  }


  grouping gobgp-neighbor-timer {
    description "additional timer";

    leaf downtime {
      type yang:timeticks;
      description
        "This timer determines the amount of time since the
        BGP last transitioned out of the Established state";
    }

    leaf update-recv-time {
      type int64;
      description
        "The number of seconds elapsed since January 1, 1970 UTC
        last time the BGP session received an UPDATE message";
    }
  }


  grouping gobgp-route-server-config {
    description
      "Configuration parameter specifying whether
      the neighbor is route server client or not.";

    leaf route-server-client {
      type boolean;
      default "false";
      description
        "Configure the neighbor as a route server client.";
    }

    leaf secondary-route {
      type boolean;
      default "false";
      description
        "if an export policy rejects a selected route, try the next route in
        order until one that is accepted is found or all routes for the peer
        are rejected.";
    }
  }

  grouping gobgp-route-server-config-set {
     description
        "set of configurations for route server client.";

    container route-server {
       description
         "Configure the local router as a route server";

      container config {
      description
        "Configuration parameters relating to route server
        client(s) used for the BGP neighbor";
      uses gobgp-route-server-config;
      }
      container state {
      config false;
      description
        "State information relating to route server
        client(s) used for the BGP neighbor";
      uses gobgp-route-server-config;
      }
    }
  }

   typedef rpki-validation-result-type {
    type enumeration {
      enum NONE {
        description "RPKI disabled";
      }
      enum NOT-FOUND {
        description "If the origin AS, prefix, maximum prefix length
        does not exist in the range of ROA";
      }
      enum VALID {
        description "If the origin AS, prefix, maximum prefix length is
        exist in the range of ROA";
      }
      enum INVALID {
        description "if the origin AS is different when prefix,
        maximum prefix length is exist in the range of ROA";
      }
    }
    description
      "indicate the validation result of RPKI based on ROA";
  }

  grouping gobgp-rpki-validation-result {
    description "additional rpki";

    leaf rpki-validation-result {
      type rpki-validation-result-type;
      default NOT-FOUND;
      description
        "specify the validation result of RPKI based on ROA as conditions";
    }
  }

  grouping gobgp-rpki-server-messages-sent {
    description "additional RPKI sent messages";

    leaf serial-query {
      type int64;
      description
        "Number of serial query message sent to RPKI server";
    }
    leaf reset-query {
      type int64;
      description
        "Number of reset query message sent to RPKI server";
    }
    leaf error {
      type int64;
      description
        "Number of error message sent to RPKI server";
    }
  }

  grouping gobgp-rpki-server-messages-received {
    description "additional RPKI receive messages";

    leaf serial-notify {
      type int64;
      description
        "Number of serial notify message received from RPKI server";
    }
    leaf cache-reset {
      type int64;
      description
        "Number of cache reset message received from RPKI server";
    }
    leaf cache-response {
      type int64;
      description
        "Number of cache response message received from RPKI server";
    }
    leaf ipv4-prefix {
      type int64;
      description
        "Number of ipv4 prefix message received from RPKI server";
    }
    leaf ipv6-prefix {
      type int64;
      description
        "Number of ipv6 prefix message received from RPKI server";
    }
    leaf end-of-data {
      type int64;
      description
        "Number of end of data message received from RPKI server";
    }
    leaf error {
      type int64;
      description
        "Number of error message received from RPKI server";
    }
  }

  grouping gobgp-rpki-server-messages {
    description "additional RPKI messages";

    container rpki-sent {
      description
        "Counters for transmission RPKI Message types";
      uses gobgp-rpki-server-messages-sent;
    }
    container rpki-received {
      description
        "Counters for reception RPKI Message types";
      uses gobgp-rpki-server-messages-received;
    }
  }

  grouping gobgp-rpki-server-state {
    description "additional RPKI state";

    leaf up {
      type boolean;
    }
    leaf serial-number {
      type uint32;
    }
    leaf records-v4 {
      type uint32;
    }
    leaf records-v6 {
      type uint32;
    }
    leaf prefixes-v4 {
      type uint32;
    }
    leaf prefixes-v6 {
      type uint32;
    }
    leaf uptime {
      type int64;
      description
        "This timer determines the amount of time since the
         RPKI last transitioned in of the Established state";
    }
    leaf downtime {
      type int64;
      description
        "This timer determines the amount of time since the
         RPKI last transitioned out of the Established state";
    }
    leaf last-pdu-recv-time {
      type int64;
      description
        "last time the received an pdu message from RPKI server";
    }
    container rpki-messages {
      description
        "Counters for transmission and reception RPKI Message types";
      uses gobgp-rpki-server-messages;
    }
  }

  grouping gobgp-rpki-server-config {
    description "additional RPKI config";

    leaf address {
      type inet:ip-address;
      description
        "Reference to the address of the RPKI server used as
         a key in the RPKI server list";
    }
    leaf port {
      type uint32;
      description
        "Reference to the port of the RPKI server";
    }
    leaf refresh-time {
      type int64;
      description
        "Check interval for a configured RPKI server.";
    }
    leaf hold-time {
      type int64;
      description
        "Specify the length of time in seconds that the session between
        the router and RPKI server is to be considered operational
        without any activity";
    }
    leaf record-lifetime {
      type int64;
      description
        "Indicate the expiration date of the route validation recode
        received from RPKI server";
    }
    leaf preference {
      type uint8;
      description
        "RPKI server has a static preference.
        Higher the preference values indicates a higher priority RPKI server";
    }
  }

  grouping gobgp-rpki-server-set {
    description "additional RPKI configuration and state";

    container config {
      description
        "Configuration parameters relating to RPKI server";
      uses gobgp-rpki-server-config;
    }
    container state {
      description
        "State information relating to RPKI server";
      uses gobgp-rpki-server-state;
    }
  }

  grouping gobgp-rpki-servers {
    description "additional RPKI structure";

    container rpki-servers {
      list rpki-server {
        key "address";
        description
          "List of RPKI servers configured on the local system";
        leaf address {
          type leafref {
            path "../config/address";
          }
        }
        uses gobgp-rpki-server-set;
      }
    }
  }

  grouping gobgp-bmp-server-config {
    description "additional BMP config";

    leaf address {
      type inet:ip-address;
      description
        "Reference to the address of the BMP server used as
         a key in the BMP server list";
    }

    leaf port {
      type uint32;
      description
        "Reference to the port of the BMP server";
    }

    leaf route-monitoring-policy {
      type bmp-route-monitoring-policy-type;
      default PRE-POLICY;
    }

    leaf statistics-timeout {
      type uint16;
      description
        "Interval seconds of statistics messages sent to BMP server";
    }

    leaf route-mirroring-enabled {
      type boolean;
      description
        "Enable feature for mirroring of received BGP messages
         mainly for debugging purpose";
    }

    leaf sys-name {
      type string;
      description
        "Reference to the SysName of the BMP server";
    }

    leaf sys-descr {
      type string;
      description
        "Reference to the SysDescr of the BMP server";
    }
  }

  grouping gobgp-bmp-server-set {
    description "additional BMP configuration and state";

    container config {
      description
        "Configuration parameters relating to BMP server";
      uses gobgp-bmp-server-config;
    }

    container state {
      description
        "Configuration parameters relating to BMP server";
      uses gobgp-bmp-server-config;
    }
  }

  grouping gobgp-bmp-servers {
    description "BGP Monitoring Protocol servers";

    container bmp-servers {
      list bmp-server {
        key "address";
        description
          "List of BMP servers configured on the local system";
        leaf address {
          type leafref {
            path "../config/address";
          }
        }
        uses gobgp-bmp-server-set;
      }
    }
  }
  grouping gobgp-vrf-common {
    description
      "Common parameters for VRF configuration and state.";

    leaf name {
      description
        "Unique name among all VRF instances.";
      type string;
    }

    leaf id {
      description
        "Unique identifier among all VRF instances.";
      type uint32;
    }

    leaf rd {
      description
        "Route Distinguisher for this VRF.";
      type string;
    }

    leaf-list import-rt {
      description
        "List of import Route Targets for this VRF.";
      type string;
    }

    leaf-list export-rt {
      description
        "List of export Route Targets for this VRF.";
      type string;
    }
  }

  grouping gobgp-vrf-config {
    description
      "Configuration parameters for VRF.";

    leaf-list both-rt {
      description
        "List of both import and export Route Targets for this VRF. Each
        configuration for import and export Route Targets will be preferred.";
      type string;
    }
  }

  grouping gobgp-vrf-set {
    description "Set of VRF instance configuration and state";

    container config {
      description
        "Configuration parameters for VRF.";
      uses gobgp-vrf-common;
      uses gobgp-vrf-config;
    }

    container state {
      description
        "Configured states of VRF.";
      uses gobgp-vrf-common;
    }
  }

  grouping gobgp-vrfs {
    description
      "Virtual Routing and Forwarding (VRF) instances.";

    container vrfs {
      list vrf {
        description
          "VRF instance configurations on the local system.";

        key "name";
        leaf name {
          type leafref {
            path "../config/name";
          }
        }

        uses gobgp-vrf-set;
      }
    }
  }

  grouping long-lived-graceful-restart {
      container long-lived-graceful-restart {
	  container config {
	      leaf enabled {
		  type boolean;
	      }
	      leaf restart-time {
		  type uint32;
	      }
	  }
	  container state {
	      leaf enabled {
		  type boolean;
	      }
	      leaf received {
		  type boolean;
	      }
	      leaf advertised {
		  type boolean;
	      }
	      leaf peer-restart-time {
		  type uint32;
	      }
        leaf running {
          type boolean;
        }
	      leaf peer-restart-timer-expired {
		      type boolean;
	      }
	  }
      }
  }

  grouping gobgp-ttl-security-config {
    description
      "Configuration parameters for TTL Security";

    leaf enabled {
      type boolean;
      default "false";
      description
        "Enable features for TTL Security";
    }

    leaf ttl-min {
      type uint8;
      description
        "Reference to the port of the BMP server";
    }
  }

  grouping gobgp-ttl-security-config-set {
    description
      "set of configurations for Generalized TTL Security Mechanism (GTSM)";

    container ttl-security {
      description
        "Configure TTL Security feature";

      container config {
        description
          "Configuration parameters for TTL Security";
        uses gobgp-ttl-security-config;
      }

      container state {
        config false;
        description
          "State information for TTL Security";
        uses gobgp-ttl-security-config;
      }
    }
  }

  // augment statements
  augment "/bgp:bgp/bgp:neighbors/bgp:neighbor/bgp:state/bgp:messages/bgp:sent" {
    description "additional counters";
    uses gobgp-message-counter;
  }

  augment "/bgp:bgp/bgp:neighbors/bgp:neighbor/bgp:state/bgp:messages/bgp:received" {
    description "additional counters";
    uses gobgp-message-counter;
  }

  augment "/bgp:bgp/bgp:neighbors/bgp:neighbor/bgp:state" {
    description "additional counters";
    uses gobgp-adjacent-table;
  }

  // The bodies of these typedefs are never used. bgpyang2golang.py maps each
  // type name to a Go type through _type_translation_map, and skips the
  // typedef itself through _typedef_exclude. They exist so that pyang can
  // resolve the references below.
  typedef bgp-capability {
      type uint8;
  }

  typedef bgp-open-message {
      type uint8;
  }

  typedef route-family {
      type uint32;
  }

  augment "/bgp:bgp/bgp:neighbors/bgp:neighbor/bgp:state" {
    leaf-list remote-capability {
      type bgp-capability;
    }
    leaf-list local-capability {
      type bgp-capability;
    }

    leaf received-open-message {
      type bgp-open-message;
    }
  }

  augment "/bgp:bgp/bgp:neighbors/bgp:neighbor/bgp:config" {
    description "additional state elements";

    leaf admin-down {
      type boolean;
      description
        "The config of administrative operation. If state, indicates the neighbor is disabled by the administrator";
    }
  }

  augment "/bgp:bgp/bgp:neighbors/bgp:neighbor/bgp:state" {
    description "additional state elements";

    leaf admin-down {
      type boolean;
      description
        "The state of administrative operation. If the state is true, it indicates the neighbor is disabled by the administrator";
    }

    leaf admin-state {
      type enumeration {
        enum UP {
          description "admin state is up";
        }
        enum DOWN {
          description "admin state is down";
        }
        enum PFX_CT {
          description "prefix counter over limit";
        }
      }
    }

    leaf established-count {
      type uint32;
      description
        "The number of how many the peer became established state";
    }

     leaf flops {
      type uint32;
      description
        "The number of flip-flops";
    }


  }

  augment "/bgp:bgp/bgp:neighbors/bgp:neighbor/bgp:config" {
    leaf neighbor-interface {
      type string;
    }
    leaf vrf {
      type string;
    }
  }

  augment "/bgp:bgp/bgp:neighbors/bgp:neighbor/bgp:state" {
    leaf neighbor-interface {
      type string;
    }
    leaf vrf {
      type string;
    }
  }

  augment "/bgp:bgp/bgp:neighbors/bgp:neighbor/bgp:state" {
    leaf remote-router-id {
        type inet:ipv4-address;
    }
  }

  augment "/bgp:bgp/bgp:neighbors/bgp:neighbor/bgp:transport/bgp:config" {
    leaf local-port {
      description "Set the local port (if available) to use for the session.";
      type inet:port-number;
    }

    leaf remote-port {
      type inet:port-number;
    }

    leaf bind-interface {
      description "Interface name for binding.";
      type string;
    }

    leaf ip-tos {
      description "IPv4 Type of Service/IPv6 Traffic Class value set on BGP TCP socket.";
      type uint8;
    }
  }

  augment "/bgp:bgp/bgp:neighbors/bgp:neighbor/bgp:timers/bgp:config" {
    description "additional timer";
    uses gobgp-timer;

    leaf connect-at-once {
      type boolean;
      default false;
      description
        "Start the first connect to the peer at once when the peer
        leaves Idle, instead of after the jittered connect delay.
        The retries still wait.";
    }
   }

  augment "/bgp:bgp/bgp:neighbors/bgp:neighbor/bgp:timers/bgp:state" {
    description "additional timers";
    uses gobgp-timer;
    uses gobgp-neighbor-timer;
   }

  augment "/bgp:bgp/bgp:neighbors/bgp:neighbor/bgp:afi-safis/bgp:afi-safi/bgp:graceful-restart/bgp:state" {
    description "additional graceful-restart status";
    leaf end-of-rib-received {
      type boolean;
    }
    leaf end-of-rib-sent {
      type boolean;
    }
    leaf running {
      type boolean;
    }
  }

  augment "/bgp:bgp/bgp:neighbors/bgp:neighbor/bgp:graceful-restart/bgp:config" {
    description "additional graceful-restart status";
    leaf deferral-time {
      type uint16;
    }
    leaf notification-enabled {
      type boolean;
    }
    leaf long-lived-enabled {
      type boolean;
    }
  }

  augment "/bgp:bgp/bgp:neighbors/bgp:neighbor/bgp:graceful-restart/bgp:state" {
    description "additional graceful-restart status";
    leaf deferral-time {
      type uint16;
    }
    leaf notification-enabled {
      type boolean;
    }
    leaf long-lived-enabled {
      type boolean;
    }
  }

  augment "/bgp:bgp/bgp:neighbors/bgp:neighbor/bgp:config" {
    leaf send-software-version {
      type boolean;
    }
  }

  augment "/bgp:bgp/bgp:peer-groups/bgp:peer-group/bgp:config" {
    leaf send-software-version {
      type boolean;
    }
  }

  augment "/bgp:bgp/bgp:peer-groups/bgp:peer-group" {
    description "route server configuration for peer-group";
    uses gobgp-route-server-config-set;
  }

  augment "/bgp:bgp/bgp:neighbors/bgp:neighbor" {
    description "route server configuration for neighbor";
    uses gobgp-route-server-config-set;
  }

  augment "/bgp:bgp/bgp:peer-groups/bgp:peer-group" {
    description "TTL Security configuration for peer-group";
    uses gobgp-ttl-security-config-set;
  }

  augment "/bgp:bgp/bgp:neighbors/bgp:neighbor" {
    description "TTL Security configuration for neighbor";
    uses gobgp-ttl-security-config-set;
   }

  augment "/rpol:routing-policy/rpol:policy-definitions/" +
    "rpol:policy-definition/rpol:statements/rpol:statement/" +
    "rpol:actions/bgp-pol:bgp-actions/bgp-pol:set-as-path-prepend" {
    description "as number used for aspath prepend";

       leaf as {
         type union {
           type inet:as-number;
           type string {
             pattern "last-as";
           }
         }
         description
           "autonomous system number or 'last-as' which means
           the leftmost as number in the AS-path to be prepended";
       }
  }

  augment "/rpol:routing-policy/rpol:defined-sets/rpol:neighbor-sets/rpol:neighbor-set" {
    description "alternative for the existing neighbor element";

    leaf-list neighbor-info {
      description
            "neighbor ip address or prefix";
      type string;
    }
  }

  // ip-prefix and rtc-prefix are mutually exclusive. That cannot be expressed
  // here: ip-prefix is a key leaf of rpol:prefix, and RFC 7950 7.8.2 says any
  // "mandatory" statement in a key leaf is ignored. Prefix.ToPrefix() rejects
  // an entry that sets both. The existing match-prefix-set condition is reused
  // for RTC (RF_RTC_UC) paths.
  augment "/rpol:routing-policy/rpol:defined-sets/rpol:prefix-sets/" +
      "rpol:prefix-set/rpol:prefix" {
    leaf rtc-prefix {
      type string {
        pattern '\d+(\.\d+)?:(\d+\.\d+\.\d+\.\d+|\d+(\.\d+)?):\d+(/\d+)?';
      }
      description
        "Route Target in RFC 4684 NLRI key form:
        <origin-as>:<route-target>[/<masklen>], where <route-target> follows
        the extended community Route Target notation. Mutually exclusive with
        ip-prefix.";
    }
  }

  augment "/rpol:routing-policy/rpol:defined-sets/" +
    "bgp-pol:bgp-defined-sets/bgp-pol:community-sets/bgp-pol:community-set" {
    description "alternative for the existing community-member";

    leaf-list community {
      description
        "community set member";
      type string;
    }
  }

  augment "/rpol:routing-policy/rpol:defined-sets/" +
    "bgp-pol:bgp-defined-sets/bgp-pol:ext-community-sets/bgp-pol:ext-community-set" {
    description "alternative for the existing ext-community-member";

    leaf-list ext-community {
      type string;
      description
        "extended community set member";
    }
  }

  augment "/rpol:routing-policy/rpol:defined-sets/" +
    "bgp-pol:bgp-defined-sets" {
    container large-community-sets {
      list large-community-set {
        key "large-community-set-name";

        leaf large-community-set-name {
          type string;
        }
        leaf-list large-community {
          type string;
          description
            "extended community set member";
        }
      }
    }
  }

  augment "/rpol:routing-policy/rpol:defined-sets/" +
    "bgp-pol:bgp-defined-sets/bgp-pol:as-path-sets/bgp-pol:as-path-set" {
    description "alternative for the existing as-path-set-member";

    leaf-list as-path {
      type string;
      description
        "AS path expression";
    }
  }

  augment "/rpol:routing-policy/rpol:policy-definitions/" +
    "rpol:policy-definition/rpol:statements/rpol:statement/" +
    "rpol:conditions/bgp-pol:bgp-conditions" {
    description "additional rpki condition";
    uses gobgp-rpki-validation-result;
  }

  deviation "/rpol:routing-policy/rpol:policy-definitions/" +
    "rpol:policy-definition/rpol:statements/rpol:statement/" +
    "rpol:conditions/bgp-pol:bgp-conditions/bgp-pol:route-type" {
    description "alternative route-type condition";
    deviate replace {
        type enumeration {
          enum NONE {
            description "route type is none";
          }
          enum INTERNAL {
            description "route type is internal";
          }
          enum EXTERNAL {
            description "route type is external";
          }
          enum LOCAL {
            description "route type is local";
          }
        }

    }
  }

  augment "/rpol:routing-policy/rpol:policy-definitions/" +
      "rpol:policy-definition/rpol:statements/rpol:statement/" +
      "rpol:conditions/bgp-pol:bgp-conditions" {
    container match-large-community-set {
      leaf large-community-set {
        type string;
      }
      uses rpol:match-set-options-group;
    }
  }

  augment "/rpol:routing-policy/rpol:policy-definitions/" +
    "rpol:policy-definition/rpol:statements/rpol:statement/" +
    "rpol:actions/bgp-pol:bgp-actions" {
    container set-large-community {
      container set-large-community-method {
        leaf-list communities {
          type string;
        }
      }
      leaf options {
        type bgp-pol:bgp-set-community-option-type;
      }
    }
  }

  augment "/bgp:bgp" {
    description "Additional RPKI configuration and state";
    uses gobgp-rpki-servers;
  }

  augment "/bgp:bgp" {
    description "Additional BMP configuration and state";
    uses gobgp-bmp-servers;
  }

  augment "/bgp:bgp" {
    description "Additional VRF configuration and state";
    uses gobgp-vrfs;
  }

  typedef mrt-type {
    type enumeration {
      enum UPDATES {
        description "RPKI disabled";
      }
      enum TABLE {
        description "If the origin AS, prefix, maximum prefix length is
        exist in the range of ROA";
      }
    }
  }

  grouping gobgp-mrt-set {
    container config {
      leaf dump-type {
        type mrt-type;
      }
      leaf file-name {
        type string;
        description
          "Configures a file name to be written";
      }
      leaf table-name {
        type inet:ip-address;
        description
          "specify the table name with route server setup";
      }
      leaf dump-interval {
        type uint64;
      }
      leaf rotation-interval {
        type uint64;
      }
    }
  }

  grouping gobgp-mrt {
    description "additional mrt configuration";
    container mrt-dump {
      list mrt {
        key "file-name";
        leaf file-name {
          type leafref {
            path "../config/file-name";
          }
        }
        uses gobgp-mrt-set;
      }
    }
  }

  augment "/bgp:bgp" {
    description "additional mrt configuration";
    uses gobgp-mrt;
  }

  grouping zebra-config {
    leaf enabled {
      type boolean;
      description
        "Configure enabling to connect to zebra.";
    }
    leaf url {
      type string;
      description
        "Configure url for zebra.";
    }
    leaf-list redistribute-route-type {
      type string;
    }
    leaf version {
      type uint8;
      description
        "Configure version of zebra protocol.  Default is 2.
        Supported version are 2 or 3 for Quagga and 4, 5 or 6 for FRRouting.";
    }
    leaf nexthop-trigger-enable {
      type boolean;
    }
    leaf nexthop-trigger-delay {
      type uint8;
    }
    leaf mpls-label-range-size {
      type uint32;
      description
        "Configure MPLS label range size which will be requested to
        FRR/Zebra.";
    }
    leaf software-name {
      type string;
      description
        "Configure zebra software name.
        frr4, cumulus, frr6, frr7, frr7.2, frr7.3, frr7.4, frr7.5, frr8, frr8.1 can be used.";
    }
  }

  grouping zebra-set {
    container zebra {
      container config {
        uses zebra-config;
      }
      container state {
        uses zebra-config;
      }
    }
  }

  augment "/bgp:bgp" {
    uses zebra-set;
  }

  grouping listen-config {
    leaf port {
        type int32;
    }
    leaf-list local-address {
        type inet:ip-address;
    }
    leaf bind-to-device {
        description "Device name for binding the BGP listener socket.";
        type string;
    }
  }

  augment "/bgp:bgp/bgp:global/bgp:config" {
      uses listen-config;
  }

  augment "/bgp:bgp/bgp:global/bgp:state" {
      uses listen-config;
  }

  grouping dynamic-neighbors {
    container dynamic-neighbors {
      list dynamic-neighbor {
        key "prefix";

        leaf prefix {
          type leafref {
            path "../config/prefix";
          }
        }

        container config {
          uses bgp-global-dynamic-neighbor-config;
        }

        container state {
          config false;
          uses bgp-global-dynamic-neighbor-config;
        }
      }
    }
  }

  grouping bgp-global-dynamic-neighbor-config {
    description "A dynamic neighbor belongs to a peer group.
     This configuration structure was taken from the latest openconfig.";

    leaf prefix {
      type inet:ip-prefix;
    }
    leaf peer-group {
      type string;
    }
  }

  augment "/bgp:bgp" {
    uses dynamic-neighbors;
  }

  grouping disable-best-path-selection-config {
    leaf disable-best-path-selection {
      type boolean;
      description
        "Disables best path selection process.";
    }
  }

  augment "/bgp:bgp/bgp:global/bgp:route-selection-options/bgp:config" {
    uses disable-best-path-selection-config;
  }

  augment "/bgp:bgp/bgp:global/bgp:route-selection-options/bgp:state" {
    uses disable-best-path-selection-config;
  }

  augment "/bgp:bgp/bgp:global/bgp:afi-safis/bgp:afi-safi" {
      uses bgp-mp:all-afi-safi-common;
  }

  grouping route-target-membership-config {
      leaf deferral-time {
        type uint16;
      }
  }

  grouping afi-safi-state {
    leaf family {
      description
        "Address family value of AFI-SAFI pair translated from afi-safi-name.";
      type route-family;
    }
  }

  augment "/bgp:bgp/bgp:global/bgp:afi-safis/bgp:afi-safi/bgp:state" {
      uses afi-safi-state;
  }

  augment "/bgp:bgp/bgp:global/bgp:afi-safis/bgp:afi-safi" {
    container route-target-membership {
      container config {
          uses route-target-membership-config;
      }
      container state {
          uses route-target-membership-config;
      }
    }

    uses long-lived-graceful-restart;
  }

  augment "/bgp:bgp/bgp:global/bgp:afi-safis/bgp:afi-safi" {
    container add-paths {
      description
        "add-paths configuration options related to a particular AFI-SAFI.";
      container config {
          uses bgp:bgp-neighbor-add-paths_config;
      }
      container state {
          uses bgp:bgp-neighbor-add-paths_config;
      }
    }
  }

  augment "/bgp:bgp/bgp:neighbors/bgp:neighbor/bgp:as-path-options/bgp:config" {
    leaf allow-as-path-loop-local {
      type boolean;
      description
        "Bypasses as-path loop detection on locally sourced (static) routes
        when exporting towards iBGP neighbors. This is needed in some environments
        where gobgp is functioning as a route injector. Non-local routes
        are still checked for as-path loops.";
    }
  }

  augment "/bgp:bgp/bgp:neighbors/bgp:neighbor/bgp:as-path-options/bgp:state" {
    leaf allow-as-path-loop-local {
      type boolean;
      description
        "Bypasses as-path loop detection on locally sourced (static) routes
        when exporting towards iBGP neighbors. This is needed in some environments
        where gobgp is functioning as a route injector. Non-local routes
        are still checked for as-path loops.";
    }
  }

  typedef bfd-session-state {
    type enumeration {
      enum UP {
        description "BFD session is up.";
      }
      enum DOWN {
        description "BFD session is down.";
      }
      enum ADMIN_DOWN {
        description "BFD session is administratively down.";
      }
      enum INIT {
        description "BFD session is in the INIT state.";
      }
    }
  }

  typedef bfd-diagnostic-code {
    type enumeration {
      enum NO_DIAGNOSTIC {
        description "No diagnostic.";
      }
      enum DETECTION_TIMEOUT {
        description "Control detection time expired.";
      }
      enum ECHO_FAILED {
        description "Echo function failed.";
      }
      enum NEIGHBOR_SIGNALED_SESSION_DOWN {
        description "Neighbor signaled session down.";
      }
      enum FORWARDING_PLANE_RESET {
        description "Forwarding plane reset.";
      }
      enum PATH_DOWN {
        description "Path down.";
      }
      enum CONCATENATED_PATH_DOWN {
        description "Concatenated path down.";
      }
      enum ADMINISTRATIVELY_DOWN {
        description "Administratively down.";
      }
      enum REVERSE_CONCATENATED_PATH_DOWN {
        description "Reverse concatenated path down.";
      }
    }
    reference "RFC 5880 §4.1";
  }

  grouping gobgp-bfd-config {
    description
      "Per-neighbor BFD session parameters (RFC 5880).";

    leaf enabled {
      type boolean;
      default "false";
      description
        "Enable BFD liveness detection for this BGP neighbor.";
    }

    leaf port {
      type uint16;
      default 3784;
      description
        "Destination UDP port for BFD control packets.
        Using a non-default port deviates from RFC 5881,
        which explicitly mandates destination UDP port 3784.";
      reference "RFC 5881 §4";
    }

    leaf desired-minimum-tx-interval {
      type uint32;
      units microseconds;
      default 1000000;
      description
        "Desired minimum transmission interval for BFD control packets.";
      reference "RFC 5880 §6.8.7";
    }

    leaf required-minimum-receive {
      type uint32;
      units microseconds;
      default 1000000;
      description
        "Required minimum receive interval for BFD control packets.";
      reference "RFC 5880 §6.8.8";
    }

    leaf detection-multiplier {
      type uint8 {
        range "1..255";
      }
      default 3;
      description
        "Detection time multiplier.";
      reference "RFC 5880 §6.8.5";
    }
  }

  grouping gobgp-bfd-state {
    description
      "Operational state leaves for a BFD session.";

    leaf session-state {
      type bfd-session-state;
      description "Local view of the BFD session state.";
    }

    leaf remote-session-state {
      type bfd-session-state;
      description "Remote view of the BFD session state.";
    }

    leaf last-failure-time {
      type uint64;
      units nanoseconds;
      description
        "Nanoseconds since the Unix epoch at which the last session failure occurred.";
    }

    leaf failure-transitions {
      type uint64;
      description "Number of UP-to-DOWN transitions.";
    }

    leaf local-discriminator {
      type uint32;
      description "Unique local discriminator for this BFD session.";
      reference "RFC 5880 §4.1";
    }

    leaf remote-discriminator {
      type uint32;
      description "Discriminator received from the remote system.";
      reference "RFC 5880 §4.1";
    }

    leaf local-diagnostic-code {
      type bfd-diagnostic-code;
      description "Diagnostic code for the last local session failure.";
    }

    leaf remote-diagnostic-code {
      type bfd-diagnostic-code;
      description "Diagnostic code received from the remote system.";
    }

    leaf remote-minimum-receive-interval {
      type uint32;
      units microseconds;
      description "Required minimum receive interval advertised by the remote system.";
    }

    container bfd-async {
      description "Counters for BFD asynchronous-mode control packets.";

      leaf last-packet-transmitted {
        type uint64;
        units nanoseconds;
        description "Nanoseconds since the Unix epoch at which the last BFD packet was transmitted.";
      }

      leaf last-packet-received {
        type uint64;
        units nanoseconds;
        description "Nanoseconds since the Unix epoch at which the last BFD packet was received.";
      }

      leaf transmitted-packets {
        type uint64;
        description "Total number of BFD control packets transmitted.";
      }

      leaf received-packets {
        type uint64;
        description "Total number of BFD control packets received.";
      }
    }
  }

  grouping gobgp-bfd-config-set {
    description
      "BFD configuration and state for a BGP neighbor or peer-group.";

    container bfd {
      description
        "Configure BFD liveness detection for this BGP neighbor.";

      container config {
        description
          "BFD configuration parameters.";
        uses gobgp-bfd-config;
      }

      container state {
        config false;
        description
          "BFD configuration and operational state.";
        uses gobgp-bfd-config;
        uses gobgp-bfd-state;
      }
    }
  }

  augment "/bgp:bgp/bgp:peer-groups/bgp:peer-group" {
    description "BFD configuration for peer-group";
    uses gobgp-bfd-config-set;
  }

  augment "/bgp:bgp/bgp:neighbors/bgp:neighbor" {
    description "BFD configuration for neighbor";
    uses gobgp-bfd-config-set;
  }

  // The keychain definitions below follow the structure of
  // openconfig-keychain 0.5.0, limited to fields supported by GoBGP.

  identity crypto-type {
    description
      "Base identify for the cryptographic algorithm";
  }

  identity hmac-sha-1-96 {
    base crypto-type;
    description
      "HMAC-SHA-1-96 keyed hash algorithm constructed from SHA-1 hash
      function and used as a HMAC, operating on 64-byte blocks of data.";
    reference
      "RFC 2404 - The Use of HMAC-SHA-1-96 within ESP and AH";
  }

  identity aes-128-cmac-96 {
    base crypto-type;
    description
      "AES-128-CMAC-96 keyed hash function based on a AES-128 block
      cipher.";
    reference
      "RFC 4494 - The AES-CMAC-96 Algorithm and Its Use with IPsec";
  }

  identity hmac-sha-256-96 {
    base crypto-type;
    description
      "HMAC-SHA-256 with a 96-bit MAC.";
  }

  identity hmac-sha-256-128 {
    base crypto-type;
    description
      "HMAC-SHA-256 with a 128-bit MAC.";
  }

  typedef keychain-ref {
    type leafref {
      path "/gobgp:keychains/gobgp:keychain/" +
           "gobgp:config/gobgp:name";
    }
    description
      "A reference to a keychain defined on the system that can be used by
      modules that require access to keychains.";
  }

  grouping keychain-base-config {
    description
      "This grouping defines key-chain parameters.";

    leaf name {
      type string;
      description
        "Keychain name.";
    }
  }

  grouping keychain-key-config {
    description "This grouping defines key-chain key parameters.";

    leaf key-id {
      type uint8;
      description
        "TCP-AO send key identifier associated with this key.";
    }

    leaf secret-key {
      type string;
      description
        "Base64-encoded TCP-AO master key.";
    }

    leaf crypto-algorithm {
      type identityref {
        base crypto-type;
      }
      description
        "Cryptographic algorithm associated with the key.  Note that not all cryptographic
        algorithms are available in all contexts (e.g., across different protocols).";
    }

    leaf receive-id {
      type uint8;
      description
        "TCP-AO receive key identifier associated with this key.";
    }

    leaf exclude-tcp-options {
      type boolean;
      description
        "Exclude TCP options from TCP-AO message authentication.";
    }
  }

  grouping keychain-key-base {
    description
      "This grouping defines keychain parameters";

    container keys {
      description
        "list of keys to be stored";

      list key {
        key "key-id";
        description
          "List of configured keys for the keychain.";

        leaf key-id {
          type leafref {
            path "../config/key-id";
          }
          description
            "Reference to key id.";
        }

        container config {
          description
            "This container defines keychain key configuration.";

          uses keychain-key-config;
        }
      }
    }
  }

  grouping keychain-common-base {
    description
      "This grouping defines keychain parameters";

    container config {
      description
        "This container defines keychain configuration.";

      uses keychain-base-config;
    }
  }

  grouping keychain-top {
    description
      "This grouping define top level structure.";

    container keychains {
      description
        "This container defines keychains.";

      list keychain {
        key "name";
        description
          "List of defined keychains.";

        leaf name {
          type leafref {
            path "../config/name";
          }
          description
            "Reference to configured keychain name";
        }

        uses keychain-common-base;
        uses keychain-key-base;
      }
    }
  }

  uses keychain-top;

  grouping gobgp-tcp-ao-config {
    description
      "TCP-AO keychain attachment for a BGP neighbor or peer-group.";

    leaf keychain {
      type keychain-ref;
      mandatory true;
      description
        "Reference to the TCP-AO keychain used by the peer.";
    }

    leaf send-id {
      type uint8;
      mandatory true;
      description
        "TCP-AO send key identifier.";
    }
  }

  grouping gobgp-tcp-ao-config-set {
    container tcp-ao {
      presence "Enables TCP-AO for the BGP transport.";
      description
        "TCP-AO configuration for a BGP neighbor or peer-group.";

      container config {
        description
          "TCP-AO configuration parameters.";
        uses gobgp-tcp-ao-config;
      }
    }
  }

  augment "/bgp:bgp/bgp:peer-groups/bgp:peer-group" {
    description "TCP-AO configuration for peer-group";
    uses gobgp-tcp-ao-config-set;
  }

  augment "/bgp:bgp/bgp:neighbors/bgp:neighbor" {
    description "TCP-AO configuration for neighbor";
    uses gobgp-tcp-ao-config-set;
  }
}
